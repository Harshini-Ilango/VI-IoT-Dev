module device-vlan-config {

    namespace "http://example.com/device-vlan-config";
    prefix "vlan";

    container vlans {
        list vlan {
            key "id";

            leaf id {
                type uint16;
            }

            leaf name {
                type string;
            }

            leaf state {
                type enumeration {
                    enum active;
                    enum inactive;
                }
            }
        }
    }
}
